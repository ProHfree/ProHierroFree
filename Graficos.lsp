;-------   S  E  R  V  I  N  C  A  D   ---------
(DEFUN ARREPLI ()
  (if (= dbl21 "1")
    (mode_tile "dbl27" 1)
    (mode_tile "dbl27" 0)
  )
  (if (= dbl22 "1")
    (mode_tile "dbl28" 1)
    (mode_tile "dbl28" 0)
  )
)
;-----------------------
(DEFUN ARREEJE ()
  (cond
    ((= dbl1 "0")
      (set_tile "dbl5" "X AxisName")
      (set_tile "dbl7" "X Dist.")
    )
    ((= dbl1 "1")
      (set_tile "dbl5" "Y AxisName")
      (set_tile "dbl7" "Y Dist.")
    )
  )
  (if peje
    (mode_tile "dbl4" 0)
    (mode_tile "dbl4" 1)
  )
)
;-----------------------
(DEFUN ARRECOL ()
  (cond
    ((/= dbl11 "2")
      (mode_tile "dbl13" 0)
      (set_tile "dblt12" "X Long.")
      (set_tile "dblt13" "Y Long.")
    )
    ((= dbl11 "2")
      (mode_tile "dbl13" 1)
      (set_tile "dblt12" "Radio")
      (set_tile "dblt13" "-------------")
    )
  )
)
;-----------------------
(DEFUN C:DIBLOSA ()
  (DIBLOSA nil)
)
;----------------------- ;PARA SETEAR A CERO EL VALOR DE PLINETYPE 2007-01-31 LC
(DEFUN DIBLOSA (peje)
  (setvar "clayer" layerdib)(setvar "cmdecho" 0)(setvar "blipmode" 0)(setvar "plinewid" 0)(setvar "osmode" os)(setvar "plinetype" 0)
  (setq opLOSA 0)
  (SETQ DCL3 (LOAD_DIALOG "graficos.dcl"))
  (SETQ CAJAB2 (NEW_DIALOG "losa" DCL3))
  
  (if (= dbl1 nil)(setq dbl1 "0"))
  (if (= dbl2 nil)(setq dbl2 "15.00"))
  (if (= dbl6 nil)(setq dbl6 "A"))
  (if (= dbl8 nil)(setq dbl8 "3.00"))
  
  (if (= dbl11 nil)(setq dbl11 "0"))
  (if (= dbl12 nil)(setq dbl12 "0.40"))
  (if (= dbl13 nil)(setq dbl13 "0.50"))
  (if (= dbl14 nil)(setq dbl14 "C1"))
  
  (if (= dbl21 nil)(setq dbl21 "1"))
  (if (= dbl22 nil)(setq dbl22 "1"))
  (if (= dbl23 nil)(setq dbl23 "2.00"))
  (if (= dbl24 nil)(setq dbl24 "P1"))
  (if (= dbl25 nil)(setq dbl25 "1.00"))
  (if (= dbl27 nil)(setq dbl27 "0.40"))
  (if (= dbl28 nil)(setq dbl28 "0.50"))
  
  (if (= dbl32 nil)(setq dbl32 "0.20"))
  (if (= dbl33 nil)(setq dbl33 "Cd1"))
  
  (ARREEJE)(ARRECOL)(ARREPLI)
  
  (foreach x (list "dbl1" "dbl2" "dbl6" "dbl8" "dbl11" "dbl12" "dbl13" "dbl14" "dbl21" "dbl22" "dbl23" "dbl24" "dbl25" "dbl27" "dbl28" "dbl32" "dbl33")
    (set_tile x (eval (read x)))
  )
  
  (foreach x '("dbl2" "dbl8")
    (action_tile x "(set (read $key) (AR $value 6 2 $key))")
  )                                 
  
  (foreach x '("dbl12" "dbl13" "dbl23" "dbl25" "dbl27" "dbl28" "dbl32")
    (action_tile x "(set (read $key) (AR $value 5 2 $key))")
  )                                 
  
  (foreach x '("dbl6" "dbl14" "dbl24" "dbl33")
    (action_tile x "(set (read $key) (AR $value 5 -1 $key))")
  )                                 
  
  (action_tile "dbl1"  "(setq dbl1  (atoa $value))(ARREEJE)")
  (action_tile "dbl11" "(setq dbl11 (atoa $value))(ARRECOL)")
  (action_tile "dbl21" "(setq dbl21 (atoa $value))(ARREPLI)")
  (action_tile "dbl22" "(setq dbl22 (atoa $value))(ARREPLI)")
  
  (action_tile "dbl9"  "(setq opLOSA 9)(done_dialog)")
  (action_tile "dbl3"  "(setq opLOSA 3)(done_dialog)")
  (action_tile "dbl4"  "(setq opLOSA 4)(done_dialog)")
  (action_tile "dbl15" "(setq opLOSA 15)(done_dialog)")
  (action_tile "dbl26" "(setq opLOSA 26)(done_dialog)")
  (action_tile "dbl34" "(setq opLOSA 34)(done_dialog)")
  (action_tile "dbl35" "(setq opLOSA 35)(done_dialog)")
  (action_tile "dbl36" "(setq opLOSA 36)(done_dialog)")
  (action_tile "dbl41" "(setq opLOSA 41)(done_dialog)")
  (action_tile "dbl42" "(setq opLOSA 42)(done_dialog)")
  (action_tile "dbl43" "(setq opLOSA 43)(done_dialog)")
  (action_tile "undoa" "(setq opLOSA 1)(done_dialog)")
  
  (START_DIALOG)
  (DONE_DIALOG)
  (cond
    ((= opLOSA 1)
      (C:PANZOON1)
      (DIBLOSA peje)
    )
    ((= opLOSA 3)
      (setvar "osmode" 0)          
      (setq peje (getpoint "\nSpecify point: "))
      (DIBLOSA peje)
    )
    ((= opLOSA 9)
      (setvar "osmode" 0)          
      (setq peje (getpoint "\nSpecify point : "))
      (if peje
	(progn
	  (if (= dbl1 "0")
	    (progn
	      (BUSCALAYER "EJES")
	      (command "_line" peje (polar peje (gra 90) (atof dbl2)) "")
	      (BUSCALAYER "EJES-TEXT")
	      (if (= dbl6 "")(setq dbl6 "A"))
	      (command "_circle" (polar peje (gra 270) 0.6) 0.25)               
	      (command "_text" "_j" "_m" (polar peje (gra 270) 0.6) 0.3 0 dbl6)
	      (command "_circle" (polar peje (gra 90) (+ 0.6 (atof dbl2))) 0.25)               
	      (command "_text" "_j" "_m" (polar peje (gra 90) (+ 0.6(atof dbl2))) 0.3 0 dbl6)
	    )
	    (progn
	      (BUSCALAYER "EJES")
	      (command "_line" peje (polar peje (gra 0) (atof dbl2)) "")
	      (BUSCALAYER "EJES-TEXT")
	      (if (= dbl6 "")(setq dbl6 "A"))
	      (command "_circle" (polar peje (gra 180) 0.6) 0.25)               
	      (command "_text" "_j" "_m" (polar peje (gra 180) 0.6) 0.3 0 dbl6)
	      (command "_circle" (polar peje (gra 0) (+ 0.6 (atof dbl2))) 0.25)               
	      (command "_text" "_j" "_m" (polar peje (gra 0) (+ 0.6(atof dbl2))) 0.3 0 dbl6)
	    )
	  )
	)
      ) 
      (DIBLOSA peje)
    )
    ((= opLOSA 4)
      (setvar "osmode" 0)          
      (if (= dbl1 "0")
	(progn
	  (BUSCALAYER "EJES")
	  (setq peje (polar peje (gra 0) (atof dbl8))) 
	  (command "_line" peje (polar peje (gra 90) (atof dbl2)) "")
	  (BUSCALAYER "EJES-TEXT")
	  (if (= dbl6 "")(setq dbl6 "A"))
	  (command "_circle" (polar peje (gra 270) 0.6) 0.25)               
	  (command "_text" "_j" "_m" (polar peje (gra 270) 0.6) 0.3 0 dbl6)
	  (command "_circle" (polar peje (gra 90) (+ 0.6 (atof dbl2))) 0.25)               
	  (command "_text" "_j" "_m" (polar peje (gra 90) (+ 0.6(atof dbl2))) 0.3 0 dbl6)
	)
	(progn
	  (BUSCALAYER "EJES")
	  (setq peje (polar peje (gra 90) (atof dbl8))) 
	  (command "_line" peje (polar peje (gra 0) (atof dbl2)) "")
	  (BUSCALAYER "EJES-TEXT")
	  (if (= dbl6 "")(setq dbl6 "A"))
	  (command "_circle" (polar peje (gra 180) 0.6) 0.25)               
	  (command "_text" "_j" "_m" (polar peje (gra 180) 0.6) 0.3 0 dbl6)
	  (command "_circle" (polar peje (gra 0) (+ 0.6 (atof dbl2))) 0.25)               
	  (command "_text" "_j" "_m" (polar peje (gra 0) (+ 0.6(atof dbl2))) 0.3 0 dbl6)
	)
      )
      (DIBLOSA peje)
    )
    ((= opLOSA 15)
      (setq p1 (getpoint "\nSpecify point : "))
      (setvar "osmode" 0)          
      (if p1
	(progn
	  (BUSCALAYER "COLUMNAS-LLENA")
	  (if (= dbl11 "1")
	    (command "_solid" (mapcar '+ p1 (list (* -0.5 (atof dbl12)) (* 0.5 (atof dbl13)))) 
			     (mapcar '+ p1 (list (* -0.5 (atof dbl12)) (* -0.5 (atof dbl13))))                
			     (mapcar '+ p1 (list (* 0.5 (atof dbl12)) (* 0.5 (atof dbl13))))                
			     (mapcar '+ p1 (list (* 0.5 (atof dbl12)) (* -0.5 (atof dbl13))))                
	    "")
	  )
	  (BUSCALAYER "COLUMNAS")
	  (if (= dbl11 "2")
	    (command "_circle" p1 (atof dbl12))
	    (command "_pline" (mapcar '+ p1 (list (* -0.5 (atof dbl12)) (* -0.5 (atof dbl13)))) 
			      (mapcar '+ p1 (list (* 0.5 (atof dbl12)) (* -0.5 (atof dbl13))))                
			      (mapcar '+ p1 (list (* 0.5 (atof dbl12)) (* 0.5 (atof dbl13))))                
			      (mapcar '+ p1 (list (* -0.5 (atof dbl12)) (* 0.5 (atof dbl13))))                
	    "_c")
	  )
	  (BUSCALAYER "TEXTOS")
	  (if (= dbl11 "2")
	    (setq p1 (mapcar '+ p1 (list (+ -0.1 (* -1.0 (atof dbl12))) (+ 0.1 (* 1.0 (atof dbl12))))) )
	    (setq p1 (mapcar '+ p1 (list (+ -0.2 (* -0.5 (atof dbl12))) (+ 0.2 (* 0.5 (atof dbl13))))) )
	  )
	  (setq p1 (list (car p1) (cadr p1) 0.0))
	  (if (= dbl14 "")(setq dbl14 "C1"))
	  (command "_text" "_j" "_m" p1 0.2 0 dbl14)
	  
	  (setq p2 (entlast))
	  (command "_change" p2 "" "_P" "_C" "8" "")
	  (command "_copy" p2 "" p1 pause)
	  (setq enttc (entlast))
	  (if (equal p1 (getvar "lastpoint"))
	    (command "_erase" enttc "")
	    (progn (command "_erase" p2 "")(setq p2 enttc))
	  ) 
	  (command "_change" p2 "" "_P" "_C" "_BYLAYER" "")
	)
      )
      (DIBLOSA peje)
    )
    ((= opLOSA 26)
      (setq p1 (getpoint "\nSpecify point : "))
      (setvar "osmode" 0)          
      (if p1
	(progn
	  (setq d1 0.0 d2 0.0)
	  (if (= dbl21 "0")
	    (setq d1  (* -1.0 (- (/ (atof dbl23) 2.0) (/ (atof dbl27) 2.0))))
	  )
	  (if (= dbl21 "2")
	    (setq d1  (* 1.0 (- (/ (atof dbl23) 2.0) (/ (atof dbl27) 2.0))))
	  )
	  (if (= dbl22 "0")
	    (setq d2  (* -1.0 (- (/ (atof dbl25) 2.0) (/ (atof dbl28) 2.0))))
	  )
	  (if (= dbl22 "2")
	    (setq d2  (* 1.0 (- (/ (atof dbl25) 2.0) (/ (atof dbl28) 2.0))))
	  )
	   
	  (setq p1 (mapcar '+ p1 (list d1 d2)))
	  (BUSCALAYER "PLINTOS")
	  (command "_pline" (mapcar '+ p1 (list (* -0.5 (atof dbl23)) (* -0.5 (atof dbl25)))) 
			    (mapcar '+ p1 (list (* 0.5 (atof dbl23)) (* -0.5 (atof dbl25))))                
			    (mapcar '+ p1 (list (* 0.5 (atof dbl23)) (* 0.5 (atof dbl25))))                
			    (mapcar '+ p1 (list (* -0.5 (atof dbl23)) (* 0.5 (atof dbl25))))                
	  "_c")
	  (BUSCALAYER "TEXTOS")
	  (setq p1 (mapcar '+ p1 (list (+ -0.2 (* -0.5 (atof dbl23))) (+ 0.2 (* 0.5 (atof dbl25))))) )
	  (setq p1 (list (car p1) (cadr p1) 0.0))
	  (if (= dbl24 "")(setq dbl24 "P1"))
	  (command "_text" "_j" "_m" p1 0.2 0 dbl24)
	  
	  (setq p2 (entlast))
	  (command "_change" p2 "" "_P" "_C" "8" "")
	  (command "_copy" p2 "" p1 pause)
	  (setq enttc (entlast))
	  (if (equal p1 (getvar "lastpoint"))
	    (command "_erase" enttc "")
	    (progn (command "_erase" p2 "")(setq p2 enttc))
	  ) 
	  (command "_change" p2 "" "_P" "_C" "_BYLAYER" "")
	)
      )
      (DIBLOSA peje)
    )
    ((= opLOSA 34)
      (setq p1 (getpoint "\nSpecify point 1 : "))
      (setq p2 (getpoint "\nSpecify point 2 : "))
      (if (and p1 p2)
	(progn
	  (BUSCALAYER "CADENAS")
	  (command "_line" p1 p2 "")
	  (setq en (entlast))
	  (command "_ucs" "_e" en)
	  (command "_copy" en "" p1 (polar p1 (gra 90) (/ (atof dbl32) 2.0)))
	  (command "_copy" en "" p1 (polar p1 (gra 270) (/ (atof dbl32) 2.0)))
	  (command "_erase" en "")
	  (command "_ucs" "")
	
	  (setq an1 (rad (angle p1 p2)))
	  (if (and (> an1 90)(<= an1 270))(setq an1 (- an1 180)))
	  (setq anT (+ an1 90))
	  (setq pm (mapcar '/ (mapcar '+ p1 p2) (list 2.0 2.0 2.0)))        
	  (setq pt (polar pm (gra anT) (+ 0.2 (* 0.5 (atof dbl32)))))
	
	  (if (= dbl33 "")(setq dbl33 "Cd1"))
	  (BUSCALAYER "TEXTOS")
	  (command "_text" "_j" "_c" pt 0.2 an1 dbl33)
	  
	  (setq p2 (entlast))
	  (command "_change" p2 "" "_P" "_C" "8" "")
	  (command "_copy" p2 "" pt pause)
	  (setq enttc (entlast))
	  (if (equal pt (getvar "lastpoint"))
	    (command "_erase" enttc "")
	    (progn (command "_erase" p2 "")(setq p2 enttc))
	  ) 
	  (command "_change" p2 "" "_P" "_C" "_BYLAYER" "")
	)
      )
      (DIBLOSA peje)
    )
    ((= opLOSA 35)
      (setq s (ssget))
      (if s 
	(while (setq stri (entsel))
	  (command "_trim" s "" stri "")
	)
      )
      (DIBLOSA peje)
    )
    ((= opLOSA 36)
      (setq s (ssget))
      (if s 
	(while (setq stri (entsel))
	  (command "_extend" s "" stri "")
	)
      )
      
      (DIBLOSA peje)
    )
    ((= opLOSA 41)
      (BUSCALAYER "LOSA")
      (command "_line" pause pause "")
      (DIBLOSA peje)
    )
    ((= opLOSA 42)
      (setq e1 (entsel "\nSelect Object : "))
      (if e1
	(progn
	  (setq p1 (getpoint "\nSpecify point to Divide Object : "))
	  (if p1
	    (progn
	      (setq p1 (osnap p1 "nea"))
	      (if p1
		(command "_break" e1 "_f" p1 p1)
	      )
	    )
	  )
	)
      )
      (DIBLOSA peje)
    )
    ((= opLOSA 43)
      (setvar "cmdecho" 1)
      (command "_stretch" "_c" pause pause "" pause pause)
      (setvar "cmdecho" 0)
      (DIBLOSA peje)
    )
  )
  (setvar "cmdecho" old2)(setvar "blipmode" blipmodeANT)(setvar "clayer" layerANT)(setvar "plinewid" wideANT)(setvar "osmode" os)(setvar "plinetype" VAR_PLINETYPE)
)
;-----------------------
(DEFUN C:DIBCORTE ()
  ;PARA SETEAR A CERO EL VALOR DE PLINETYPE 2007-01-31 LC
  (setvar "clayer" layerdib)(setvar "cmdecho" 0)(setvar "blipmode" 0)(setvar "plinewid" 0)(setvar "osmode" 0)(setvar "plinetype" 0)
  (setq opCORTE 0)
  (SETQ DCL3 (LOAD_DIALOG "graficos.dcl"))
  (SETQ CAJAB2 (NEW_DIALOG "corte" DCL3))
  
  (foreach x '("in1" "in2" "in3" "in4" "in5" "in6" "in7" "in8" "in9" "in10" "in11" "in12")
    (tipogra2 x "in" x 0)
    (action_tile x "(setq qq $key opCORTE 1)(done_dialog)")
  )                                 

  (START_DIALOG)
  (DONE_DIALOG)
  (cond
    ((= opCORTE 1)
      (command "_insert" qq pause 1 1 0)
      (command "_explode" "_l")
      (C:DIBCORTE)
    )
  )
  (setvar "cmdecho" old2)(setvar "blipmode" blipmodeANT)(setvar "clayer" layerANT)(setvar "plinewid" wideANT)(setvar "osmode" os)(setvar "plinetype" VAR_PLINETYPE)
)
;-----------------------
(DEFUN BUSCALAYER (layo / l1 pipo)
  (setq pipo 0 l1 (tblnext "layer" t))
  (while l1
    (setq l1 (cdr (assoc 2 l1)))
    (if (eq layo l1)(setq pipo 1))
    (setq l1 (tblnext "layer"))
  )
  (if (= pipo 1)
    (setvar "clayer" layo)
    (setvar "clayer" "0")
  )
)
;-----------------------
(DEFUN C:DIBMARCAS (/ p1 p2 pp1 p12)
  ;PARA SETEAR A CERO EL VALOR DE PLINETYPE 2007-01-31 LC
  (setvar "clayer" layerdib)(setvar "cmdecho" 0)(setvar "blipmode" 0)(setvar "plinewid" 0)(setvar "osmode" 0)(setvar "plinetype" 0)
  (setq opMARCAS 0)
  (SETQ DCL3 (LOAD_DIALOG "graficos.dcl"))
  (SETQ CAJAB2 (NEW_DIALOG "marcas" DCL3))
  
  (if (= espxx nil)(setq espxx "0.50"))
  (if (= espyy nil)(setq espyy "0.50"))
  (if (= mll12 nil)(setq mll12 1))
  (if (= mll3  nil)(setq mll3  "0.08"))
  
  (set_tile "espx" espxx)
  (set_tile "espy" espyy)
  
  (if (= mll12 1)(set_tile "mll1" "1"))
  (if (= mll12 2)(set_tile "mll2" "1"))
  (set_tile "mll3" mll3)
  
  (action_tile "espx" "(setq espxx (AR $value 5 2 \"espx\")  )")
  (action_tile "espy" "(setq espyy (AR $value 5 2 \"espy\")  )")
  (action_tile "mll3" "(setq mll3  (AR $value 5 2 \"mll3\")  )")
  
  (action_tile "mll1" "(setq mll12 1)")
  (action_tile "mll2" "(setq mll12 2)")
  
  (action_tile "ml1" "(setq opMARCAS 1)(done_dialog)")
  (action_tile "ml2" "(setq opMARCAS 2)(done_dialog)")
  (action_tile "ml3" "(setq opMARCAS 3)(done_dialog)")
  
  (START_DIALOG)
  (DONE_DIALOG)
  (cond
    ((= opMARCAS 1)
      (BUSCALAYER "LINEA-DONA")
      (command "_donut" 0 0.05 "_nea" pause "")
      (setq p1 (getvar "lastpoint"))
      (command "_line" p1 pause "")
      (C:DIBMARCAS)
    )
    ((or (= opMARCAS 2)(= opMARCAS 3))
      (setvar "clayer" layerdib)
      (setq p1 nil opAL "Punto")

      (while (or (= opAL "Undo")(= opAL "Punto")(and (= opAL "Continuar")(/= p1 nil)))
	(cond
	  ((= opAL "Undo")
	    (command "_undo" "")
	    (command "_undo" "")
	  )
	  ((= opAL "Punto")
	    (setq p12 (getpoint "\nSpecify point [nea]: "))
	    (if p12 (setq p12 (osnap p12 "nea")))
	    (if (= p1 nil)
	      (setq pp1 p12)
	      (if p12 (command "_pan" p12 p1))
	    )
	    (setq p1 p12)
	    (if p1
	      ;(progn
		(if (= mll12 1)
		  (if (= opMARCAS 2)
		    (command "_line" (polar p1 (gra 90) (/ (atof mll3) 2.0)) (polar p1 (gra 270) (/ (atof mll3) 2.0)) "")
		    (command "_line" (polar p1 (gra 0) (/ (atof mll3) 2.0)) (polar p1 (gra 180) (/ (atof mll3) 2.0)) "")
		  )
		  (command "_donut" 0 (/ (atof mll3) 2.0) p1 "")
		)
	      ;)
	    )
	  )
	  ((= opAL "Continuar")
	    (if (= opMARCAS 2)
	      (setq p2 (polar p1 (gra 0) (atof espxx)))
	      (setq p2 (polar p1 (gra 90) (atof espyy)))
	    )
	    (if (= mll12 1)
	      (if (= opMARCAS 2)
		(command "_line" (polar p2 (gra 90) (/ (atof mll3) 2.0)) (polar p2 (gra 270) (/ (atof mll3) 2.0)) "")
		(command "_line" (polar p2 (gra 0) (/ (atof mll3) 2.0)) (polar p2 (gra 180) (/ (atof mll3) 2.0)) "")
	      )
	      (command "_donut" 0 (/ (atof mll3) 2.0) p2 "")
	    )  
	    (command "_pan" p2 p1)
	    (setq p1 p2)
	  )
	)
	(INITGET "Point Continue Exit Undo")
	(if p1
	  (progn
	    (setq opAL (GETKWORD "\nSelect option : Point/<Continue>/Exit/Undo : "))
	    (if (= opAL nil)(setq opAL "Continuar"))
	  )
	  (progn
	    (setq opAL (GETKWORD "\nSelect option : <Point>/Continue/Exit/Undo : "))
	    (if (= opAL nil)(setq opAL "Punto"))
	  )
	)
      )
      (if (and p1 pp1) (command "_pan" pp1 p1))
      (C:DIBMARCAS)
    )
  )
  (setvar "cmdecho" old2)(setvar "blipmode" blipmodeANT)(setvar "clayer" layerANT)(setvar "plinewid" wideANT)(setvar "osmode" os)(setvar "plinetype" VAR_PLINETYPE)
)
;-----------------------
(DEFUN ARREVIGAS ()
  (cond
    ((= vicol "0")
      (mode_tile "vc1" 0)
      (set_tile "vct2" "Height Beam")
      (set_tile "vct1" "Y Factor")
      (set_tile "vct0" "Column Dist.")
      (set_tile "vct3" "X Vain Dist.")
      (set_tile "vct4" "Column Low")
      (set_tile "vct5" "Column Top")
      (set_tile "vct6" "  Columns  ")
      (TIPOGRA2 "cinf" "colum" "vci1" 0)
      (TIPOGRA2 "csup" "colum" "vci2" 0)
      (TIPOGRA2 "call" "colum" "vci3" 0)	
    )
    ((= vicol "1")
      (mode_tile "vc1" 1)
      (set_tile "vct2" "Column Wide")
      (set_tile "vct1" "----------------")
      (set_tile "vct0" "Beam Dist.")
      (set_tile "vct3" "Y Vain Dist.")
      (set_tile "vct4" "  Left Beam ")
      (set_tile "vct5" "  Right Beam ")
      (set_tile "vct6" "   Beams    ")
      (TIPOGRA2 "vizq" "colum" "vci1" 0)
      (TIPOGRA2 "vder" "colum" "vci2" 0)
      (TIPOGRA2 "vall" "colum" "vci3" 0)		
    )
  )
  (if pvig
    (foreach x (list "vc4" "vc5" "vc6" "vc7" "vc8" "vca")  
      (mode_tile x 0)
    )
    (foreach x (list "vc4" "vc5" "vc6" "vc7" "vc8" "vca")  
      (mode_tile x 1)
    )
  )
  (if pvig
    (if (= abrir 0)
      (progn
	(mode_tile "vc7" 1)
	(mode_tile "vca" 0)
	(mode_tile "vc8" 1)
      )
      (progn
	(mode_tile "vc7" 0)
	(mode_tile "vca" 1)
	(mode_tile "vc8" 0)
      )
    )
  )
)
;-----------------------
(DEFUN C:PARTIDO (punto angulo dvc / por1 por2 por3 por4 ppp)
  (setq por1 (* 0.40 dvc) por2 (* 0.20 dvc) por3 (* 0.20 dvc) por4 (* 0.30 dvc))
  (setq ppp (polar punto (gra 180) por3))
  
  (command "_pline" ppp 
		   (setq ppp (mapcar '+ ppp (list (+ por3 por4) 0.0)))
		   (setq ppp (mapcar '+ ppp (list por2 por1)))
		   (setq ppp (mapcar '+ ppp (list 0.0 (* por1 -2.0))))
		   (setq ppp (mapcar '+ ppp (list por2 por1)))
		   (setq ppp (mapcar '+ ppp (list (+ por4 por3) 0.0)))
  "")
  (command "_rotate" (entlast) "" punto angulo)
)
;-----------------------
(DEFUN C:DIBVIGAS ()
  (setq abrir 0)
  (DIBVIGAS nil)
)
;-----------------------
(DEFUN DIBVIGAS (pvig)
  ;PARA SETEAR A CERO EL VALOR DE PLINETYPE 2007-01-31 LC
  (setvar "clayer" layerdib)(setvar "cmdecho" 0)(setvar "blipmode" 0)(setvar "plinewid" 0)(setvar "osmode" 0)(setvar "plinetype" 0)
  (setq opVIGAS 0)
  (SETQ DCL3 (LOAD_DIALOG "graficos.dcl"))
  (SETQ CAJAB2 (NEW_DIALOG "vigas" DCL3))
;  (foreach x '("vci1" "vci2" "vci3")
;    (tipogra2 x "colum" x 0)
;  )    
  (if (= vc0 nil)(setq vc0 "0.40")) 
  (if (= vc1 nil)(setq vc1 "2.00")) 
  (if (= vc2 nil)(setq vc2 "0.20"))
  (if (= vc3 nil)(setq vc3 "2.00"))
  (if (= vicol nil)(setq vicol "0"))
  
  (set_tile "vc0" vc0)
  (set_tile "vc1" vc1)
  (set_tile "vc2" vc2)
  (set_tile "vc3" vc3)
  (set_tile "vc9" vicol)
  (ARREVIGAS)

  (action_tile "vc0" "(setq vc0  (AR $value 5 2 \"vc0\")  )")
  (action_tile "vc1" "(setq vc1  (AR $value 5 2 \"vc1\")  )")
  (action_tile "vc2" "(setq vc2  (AR $value 5 2 \"vc2\")  )")
  (action_tile "vc3" "(setq vc3  (AR $value 5 2 \"vc3\")  )")
  (action_tile "vc9" "(setq vicol (atoa $value))(ARREVIGAS)")
  
  (action_tile "vc4" "(setq opVIGAS 4)(done_dialog)")
  (action_tile "vc5" "(setq opVIGAS 5)(done_dialog)")
  (action_tile "vc6" "(setq opVIGAS 6)(done_dialog)")
  (action_tile "vc7" "(setq opVIGAS 7)(done_dialog)")
  (action_tile "vca" "(setq opVIGAS 7.7)(done_dialog)")
  (action_tile "vc8" "(setq opVIGAS 8)(done_dialog)")
  (action_tile "vcp" "(setq opVIGAS 3)(done_dialog)")
  
  (START_DIALOG)
  (DONE_DIALOG)
  (cond
    ((= opVIGAS 3)
      (setq pviggg (getpoint "\nSpecify point : "))
      (if (and pvig pviggg)(command "_pan" pviggg pvig))
      (setq pvig pviggg)
      (DIBVIGAS pvig)
    )
    ((= opVIGAS 5)
      (setvar "clayer" layerdib)
      (if (= vicol "0")
	(progn
	  (command "_line" pvig (polar pvig (gra 0) (atof vc0)) "")
	  (command "_line" (polar pvig (gra 90) (* (atof vc2)(atof vc1))) (polar pvig (gra 90) (* 2.0 (atof vc2)(atof vc1)))  "")
	  (command "_copy" (entlast) "" pvig (polar pvig (gra 0) (atof vc0)))
	  (BUSCALAYER "CORTAR")
	  (c:partido (polar pvig (gra 90) (* 2.0 (atof vc2)(atof vc1))) 0 (atof vc0))
	  (BUSCALAYER "EJES")
	  (command "_line" (mapcar '+ pvig (list (/ (atof vc0) 2.0) (* -2.0 (atof vc2)(atof vc1)))) (setq punviga (mapcar '+ pvig (list (/ (atof vc0) 2.0) (* 3.0 (atof vc2)(atof vc1))))) "")

	  (BUSCALAYER "EJES-TEXT")
	  (setq nomviga (getstring "\nAxis Name <A> : "))
	  (if (= nomviga "")(setq nomviga "A"))
	  (command "_circle" (polar punviga (gra 90) 0.6) 0.25)               
	  (command "_text" "_j" "_m" (polar punviga (gra 90) 0.6) 0.3 0 nomviga)

	  (setq pvigg (polar pvig (gra 0) (atof vc0)))
	  (command "_pan" pvigg pvig)
	  (setq pvig pvigg)
	)
	(progn
	  (command "_line" pvig (polar pvig (gra 90) (atof vc0)) "")
	  (command "_line" (polar pvig (gra 0) (atof vc2)) (polar pvig (gra 0) (* 2.0 (atof vc2)))  "")
	  (command "_copy" (entlast) "" pvig (polar pvig (gra 90) (atof vc0)))
	  (BUSCALAYER "CORTAR")
	  (c:partido (polar pvig (gra 0) (* 2.0 (atof vc2))) 90 (atof vc0))
	  (BUSCALAYER "EJES")
	  (command "_line" (mapcar '+ pvig (list (* -2.0 (atof vc2)) (/ (atof vc0) 2.0))) (mapcar '+ pvig (list (* 3.0 (atof vc2)) (/ (atof vc0) 2.0))) "")
	  (setq pvigg (polar pvig (gra 90) (atof vc0)))
	  (command "_pan" pvigg pvig)
	  (setq pvig pvigg)
	)
      )
      (DIBVIGAS pvig)
    )
    ((= opVIGAS 4)
      (setvar "clayer" layerdib)
      (if (= vicol "0")
	(progn
	  (command "_line" (polar pvig (gra 90) (* (atof vc2)(atof vc1))) (mapcar '+ pvig (list (atof vc0) (* (atof vc2)(atof vc1)))) "")
	  (command "_line" pvig (polar pvig (gra 270) (* (atof vc2)(atof vc1))) "")
	  (command "_copy" (entlast) "" pvig (polar pvig (gra 0) (atof vc0)))
	  (BUSCALAYER "CORTAR")
	  (c:partido (polar pvig (gra 270) (* (atof vc2)(atof vc1))) 0 (atof vc0))
	  (BUSCALAYER "EJES")
	  (command "_line" (mapcar '+ pvig (list (/ (atof vc0) 2.0) (* -2.0 (atof vc2)(atof vc1)))) (setq punviga (mapcar '+ pvig (list (/ (atof vc0) 2.0) (* 3.0 (atof vc2)(atof vc1))))) "")

	  (BUSCALAYER "EJES-TEXT")
	  (setq nomviga (getstring "\nAxis Name <A> : "))
	  (if (= nomviga "")(setq nomviga "A"))
	  (command "_circle" (polar punviga (gra 90) 0.6) 0.25)               
	  (command "_text" "_j" "_m" (polar punviga (gra 90) 0.6) 0.3 0 nomviga)
	  
	  (setq pvigg (polar pvig (gra 0) (atof vc0)))
	  (command "_pan" pvigg pvig)
	  (setq pvig pvigg)
	)
	(progn
	  (command "_line" (polar pvig (gra 0) (atof vc2)) (mapcar '+ pvig (list (atof vc2) (atof vc0))) "")
	  (command "_line" pvig (polar pvig (gra 180) (atof vc2)) "")
	  (command "_copy" (entlast) "" pvig (polar pvig (gra 90) (atof vc0)))
	  (BUSCALAYER "CORTAR")
	  (c:partido (polar pvig (gra 180) (atof vc2)) 90 (atof vc0))
	  (BUSCALAYER "EJES")
	  (command "_line" (mapcar '+ pvig (list (* -2.0 (atof vc2)) (/ (atof vc0) 2.0))) (mapcar '+ pvig (list (* 3.0 (atof vc2)) (/ (atof vc0) 2.0))) "")
	  (setq pvigg (polar pvig (gra 90) (atof vc0)))
	  (command "_pan" pvigg pvig)
	  (setq pvig pvigg)
	)
      )
      (DIBVIGAS pvig)
    )
    ((= opVIGAS 6)
      (if (= vicol "0")
	(progn
	  (command "_line" (polar pvig (gra 90) (* (atof vc2)(atof vc1))) (polar pvig (gra 90) (* 2.0 (atof vc2)(atof vc1)))  "")
	  (command "_copy" (entlast) "" pvig (polar pvig (gra 0) (atof vc0)))
	  (BUSCALAYER "CORTAR")
	  (c:partido (polar pvig (gra 90) (* 2.0 (atof vc2)(atof vc1))) 0 (atof vc0))
	  
	  (setvar "clayer" layerdib)
	  (command "_line" pvig (polar pvig (gra 270) (* (atof vc2)(atof vc1))) "")
	  (command "_copy" (entlast) "" pvig (polar pvig (gra 0) (atof vc0)))
	  (BUSCALAYER "CORTAR")
	  (c:partido (polar pvig (gra 270) (* (atof vc2)(atof vc1))) 0 (atof vc0))
	  (BUSCALAYER "EJES")
	  (command "_line" (mapcar '+ pvig (list (/ (atof vc0) 2.0) (* -2.0 (atof vc2)(atof vc1)))) (setq punviga (mapcar '+ pvig (list (/ (atof vc0) 2.0) (* 3.0 (atof vc2)(atof vc1))))) "")

	  (BUSCALAYER "EJES-TEXT")
	  (setq nomviga (getstring "\nAxis Name <A> : "))
	  (if (= nomviga "")(setq nomviga "A"))
	  (command "_circle" (polar punviga (gra 90) 0.6) 0.25)               
	  (command "_text" "_j" "_m" (polar punviga (gra 90) 0.6) 0.3 0 nomviga)
		    
	  (setq pvigg (polar pvig (gra 0) (atof vc0)))
	  (command "_pan" pvigg pvig)
	  (setq pvig pvigg)
	)
	(progn
	  (command "_line" (polar pvig (gra 0) (atof vc2)) (polar pvig (gra 0) (* 2.0 (atof vc2)))  "")
	  (command "_copy" (entlast) "" pvig (polar pvig (gra 90) (atof vc0)))
	  (BUSCALAYER "CORTAR")
	  (c:partido (polar pvig (gra 0) (* 2.0 (atof vc2))) 90 (atof vc0))
	  
	  (setvar "clayer" layerdib)
	  (command "_line" pvig (polar pvig (gra 180) (atof vc2)) "")
	  (command "_copy" (entlast) "" pvig (polar pvig (gra 90) (atof vc0)))
	  (BUSCALAYER "CORTAR")
	  (c:partido (polar pvig (gra 180) (atof vc2)) 90 (atof vc0))
	  (BUSCALAYER "EJES")
	  (command "_line" (mapcar '+ pvig (list (* -2.0 (atof vc2)) (/ (atof vc0) 2.0))) (mapcar '+ pvig (list (* 3.0 (atof vc2)) (/ (atof vc0) 2.0))) "")
	  (setq pvigg (polar pvig (gra 90) (atof vc0)))
	  (command "_pan" pvigg pvig)
	  (setq pvig pvigg)
	)
      )
      (DIBVIGAS pvig)
    )
    ((= opVIGAS 7)
      (setvar "clayer" layerdib)
      (if (= vicol "0")
	(command "_line" pvig (polar pvig (gra 90) (* (atof vc2) (atof vc1))) "")
	(command "_line" pvig (polar pvig (gra 0) (atof vc2)) "")
      )
      (if (and pviggg pvig)(command "_pan" pviggg pvig))
      (setq abrir 0)
      (DIBVIGAS nil)
    )
    ((= opVIGAS 7.7)
      (setvar "clayer" layerdib)
      (if (= vicol "0")
	(progn
	  (command "_line" pvig (polar pvig (gra 90) (* (atof vc2) (atof vc1))) "")
	  (setq nomviga (getstring "\nBeam Name <V1> : "))
	  (if (= nomviga "")(setq nomviga "V1"))
	  (BUSCALAYER "TEXTOS")
	  (command "_text" "_j" "_m" (mapcar '+ pvig (list -0.6 (* 0.5 (atof vc2) (atof vc1)))) 0.3 0 nomviga)
	)
	(progn
	  (command "_line" pvig (polar pvig (gra 0) (atof vc2)) "")
	  (setq nomviga (getstring "\nColumn Name <C1> : "))
	  (if (= nomviga "")(setq nomviga "C1"))
	  (BUSCALAYER "TEXTOS")
	  (command "_text" "_j" "_m" (mapcar '+ pvig (list (* 0.5 (atof vc2)) -0.6)) 0.3 0 nomviga)
	)
      )
      (setq abrir 1)
      (DIBVIGAS pvig)
    )
    ((= opVIGAS 8)
      (setvar "clayer" layerdib)
      (if (= vicol "0")
	(progn
	  (command "_line" pvig (polar pvig (gra 0) (atof vc3)) "")
	  (command "_copy" (entlast) "" pvig (polar pvig (gra 90) (* (atof vc2)(atof vc1))))
	  (setq pvigg (polar pvig (gra 0) (atof vc3)))
	  (command "_pan" pvigg pvig)
	  (setq pvig pvigg)
	)
	(progn
	  (command "_line" pvig (polar pvig (gra 90) (atof vc3)) "")
	  (command "_copy" (entlast) "" pvig (polar pvig (gra 0) (atof vc2)))
	  (setq pvigg (polar pvig (gra 90) (atof vc3)))
	  (command "_pan" pvigg pvig)
	  (setq pvig pvigg)
	)
      )
      (DIBVIGAS pvig)
    )
  )
  (setvar "cmdecho" old2)(setvar "blipmode" blipmodeANT)(setvar "clayer" layerANT)(setvar "plinewid" wideANT)(setvar "osmode" os)(setvar "plinetype" VAR_PLINETYPE)
)
;-----------------------
(DEFUN ARREESTRIBOS ()
  (cond
    ((= vicole "0")
      (set_tile "evct1" "Left@ expart.")
      (set_tile "evct2" "Cen@ expart.")
      (set_tile "evct3" "Right@ expart.")
      (set_tile "evct4" "Left% Porcen. ")
      (set_tile "evct5" "Cen% Porcen. ")
      (set_tile "evct6" "Right% Porcen. ")
    )
    ((= vicole "1")
      (set_tile "evct1" "Low@ expart.")
      (set_tile "evct2" "Cen@ expart.")
      (set_tile "evct3" "Top@ expart.")
      (set_tile "evct4" "Porcen. Low% Porcen.")
      (set_tile "evct5" "Porcen. Cen% Porcen.")
      (set_tile "evct6" "Porcen. Top% Porcen.")
    )
  )
)
;-----------------------
(DEFUN C:DIBESTRIBOS (/ l1 l2 l3 lt ht pip1 pip2 p1 p2 p1x p2x p1y p2y pp1)
  ;PARA SETEAR A CERO EL VALOR DE PLINETYPE 2007-01-31 LC
  (setvar "clayer" layerdib)(setvar "cmdecho" 0)(setvar "blipmode" 0)(setvar "plinewid" 0)(setvar "osmode" os)(setvar "plinetype" 0)
  (setq opESTRIBOS 0)
  (SETQ DCL3 (LOAD_DIALOG "graficos.dcl"))
  (SETQ CAJAB2 (NEW_DIALOG "estribos" DCL3))
  
  (if (= vicole nil)(setq vicole "0"))
  (if (= evc7 nil)(setq evc7 "0.34"))
  (if (= evc1 nil)(setq evc1 "0.10"))
  (if (= evc2 nil)(setq evc2 "0.20"))
  (if (= evc3 nil)(setq evc3 "0.10"))
  (if (= evc4 nil)(setq evc4 "25"))
  (if (= evc5 nil)(setq evc5 "50"))
  (if (= evc6 nil)(setq evc6 "25"))
  
  (set_tile "vicole" vicole)
  (set_tile "evc7" evc7)
  (set_tile "evc1" evc1)
  (set_tile "evc2" evc2)
  (set_tile "evc3" evc3)
  (set_tile "evc4" evc4)
  (set_tile "evc5" evc5)
  (set_tile "evc6" evc6)
  (ARREESTRIBOS)

  (action_tile "vicole" "(setq vicole (atoa $value))(ARREESTRIBOS)")
  (action_tile "evc7" "(setq evc7 (AR $value 5 2 \"evc7\")  )")
  (action_tile "evc1" "(setq evc1 (AR $value 5 2 \"evc1\")  )")
  (action_tile "evc2" "(setq evc2 (AR $value 5 2 \"evc2\")  )")
  (action_tile "evc3" "(setq evc3 (AR $value 5 2 \"evc3\")  )")
  (action_tile "evc4" "(setq evc4 (AR $value 5 0 \"evc4\")  )")
  (action_tile "evc5" "(setq evc5 (AR $value 5 0 \"evc5\")  )")
  (action_tile "evc6" "(setq evc6 (AR $value 5 0 \"evc6\")  )")
  
  (action_tile "evcd" "(setq opESTRIBOS 1)(done_dialog)")
  
  (START_DIALOG)
  (DONE_DIALOG)
  (cond
    ((and (= vicole "0")(= opESTRIBOS 1))
      (setq p1 (getpoint "\nSpecify point 1 : "))
      (setq p2 (getpoint "\nSpecify point 2 : "))

      (setvar "osmode" 0)
      (if (and p1 p2)
	(progn
	  (setq p1x (car p1) p1y (cadr p1))
	  (setq p2x (car p2) p2y (cadr p2))
	  (if (> p1x p2x)(setq p3x p1x p1x p2x p2x p3x))
	  (if (> p1y p2y)(setq p3y p1y p1y p2y p2y p3y))
	  (setq p1 (list p1x p1y) p2 (list p2x p2y))
	  (setq lt (- p2x p1x) ht (- p2y p1y))
	  (setq l1 (* (atof evc4) lt 0.01) l2 (* (atof evc5) lt 0.01) l3 (* (atof evc6) lt 0.01))
	  
	  (if (> l1 0)
	    (progn
	      (setq pp1 (polar p1 (gra 90) (/ (- ht (atof evc7)) 2.0)))
	      (command "_line" pp1 (polar pp1 (gra 90) (atof evc7)) "")
	      (setq el (entlast))
	      (setq dl (+ p1x (atof evc1)))
	      (while (<= dl (+ p1x (atof evc1) l1 -0.01))
		(command "_copy" el "" p1 (list dl p1y))
		(setq pip1 dl)
		(setq dl (+ dl (atof evc1)))
	      )
	    )
	  )

	  (if (> l3 0)
	    (progn
	      (setq pp1 (polar p2 (gra 270) (/ (- ht (atof evc7)) 2.0)))
	      (command "_line" pp1 (polar pp1 (gra 270) (atof evc7)) "")
	      (setq el (entlast))
	      (setq dl (- p2x (atof evc3)))
	      (while (>= dl (- p2x (atof evc1) l3 -0.01))
		(command "_copy" el "" p2 (list dl p2y))
		(setq pip2 dl)
		(setq dl (- dl (atof evc3)))
	      )
	    )
	  )

	  (if (and (> l1 0) (> l2 0) (> l3 0))
	    (progn
	      (setq pip1 (+ pip1 (atof evc2)))
	      (setq pip2 (- pip2 (atof evc2)))
	      (setq lpip (- pip2 pip1))
	      (setq npip (fix (+ (/ lpip (atof evc2)) 0.01)))
	      (setq pp1 (list (+ pip1 (/ (- lpip (* npip (atof evc2))) 2.0)) (+ p1y (/ (- ht (atof evc7)) 2.0))  ))
	      (command "_line" pp1 (polar pp1 (gra 90) (atof evc7)) "")
	      (setq el (entlast))
	      (setq dl (+ (car pp1) (atof evc2)))
	      (while (<= dl (+ pip2 0.01))
		(command "_copy" el "" pp1 (list dl (cadr pp1)))
		(setq dl (+ dl (atof evc2)))
	      )
	    )
	  )
	  (BUSCALAYER "COTAS")
	  (setq p1 (polar p1 (gra 270) 0.7))
	  (setq p2 (polar p1 (gra 0) l1))
	  (setq p3 (polar p2 (gra 0) l2))
	  (setq p4 (polar p3 (gra 0) l3))
	  (if (> l1 0)
	    (progn
	      (command "_line" (polar p1 (gra 270) 0.10) (polar p1 (gra 90) 0.10) "")
	      (command "_rotate" (entlast) "" p1 -45)
	      (command "_line" (polar p2 (gra 270) 0.10) (polar p2 (gra 90) 0.10) "")
	      (command "_rotate" (entlast) "" p2 -45)
	      (command "_line" (polar p1 (gra 270) 0.10) (polar p1 (gra 90) 0.10) "")
	      (command "_line" (polar p2 (gra 270) 0.10) (polar p2 (gra 90) 0.10) "")
	      (command "_line" p1 p2 "")
	      ;SE ACUALIZO LA VARIABLE DE t POR t7 POR DAR ERROR DE PROTECION DE VARIABLE 2007-02-01 LC
	      (setq t7 (/ 100.0 (atof evc4)))
	      (if (= t7 (fix t7))(setq t7 (strcat "L/" (rtos t7 2 0)))(setq t7 (strcat "L/" (rtos t7 2 2))))
	      (if (eq t7 "L/1")(setq t7 "L"))
	      (setq p (mapcar '/ (mapcar '+ p1 p2) (list 2.0 2.0 2.0)))
	      (command "_text" "_j" "_c" (polar p (gra 90) 0.15) 0.10 0 t7)
	      (command "_text" "_j" "_c" (polar p (gra 90) -0.25) 0.10 0 (strcat "@" (substr evc1 2 5)))
	    )
	  )
	  (if (> l3 0)
	    (progn
	      (command "_line" (polar p3 (gra 270) 0.10) (polar p3 (gra 90) 0.10) "")
	      (command "_rotate" (entlast) "" p3 -45)
	      (command "_line" (polar p4 (gra 270) 0.10) (polar p4 (gra 90) 0.10) "")
	      (command "_rotate" (entlast) "" p4 -45)
	      (command "_line" (polar p3 (gra 270) 0.10) (polar p3 (gra 90) 0.10) "")
	      (command "_line" (polar p4 (gra 270) 0.10) (polar p4 (gra 90) 0.10) "")
	      (command "_line" p3 p4 "")
	      ;SE ACUALIZO LA VARIABLE DE t POR t7 POR DAR ERROR DE PROTECION DE VARIABLE 2007-02-01 LC
	      (setq t7 (/ 100.0 (atof evc6)))
	      (if (= t7 (fix t7))(setq t7 (strcat "L/" (rtos t7 2 0)))(setq t7 (strcat "L/" (rtos t7 2 2))))
	      (if (eq t7 "L/1")(setq t7 "L"))
	      (setq p (mapcar '/ (mapcar '+ p3 p4) (list 2.0 2.0 2.0)))
	      (command "_text" "_j" "_c" (polar p (gra 90) 0.15) 0.10 0 t7)
	      (command "_text" "_j" "_c" (polar p (gra 90) -0.25) 0.10 0 (strcat "@" (substr evc3 2 5)))
	    )
	  )
	  (if (and (> l1 0) (> l2 0) (> l3 0))
	    (progn
	      (command "_line" p2 p3 "")
	      ;SE ACUALIZO LA VARIABLE DE t POR t2 POR DAR ERROR DE PROTECION DE VARIABLE 2007-02-01 LC
	      (setq t7 (/ 100.0 (atof evc5)))
	      (if (= t7 (fix t7))(setq t7 (strcat "L/" (rtos t7 2 0)))(setq t7 (strcat "L/" (rtos t7 2 2))))
	      (if (eq t7 "L/1")(setq t7 "L"))
	      (setq p (mapcar '/ (mapcar '+ p2 p3) (list 2.0 2.0 2.0)))
	      (command "_text" "_j" "_c" (polar p (gra 90) 0.15) 0.10 0 t7)
	      (command "_text" "_j" "_c" (polar p (gra 90) -0.25) 0.10 0 (strcat "@" (substr evc2 2 5)))
	    )
	  )
	)
      )
      (C:DIBESTRIBOS)
    )
    ((and (= vicole "1")(= opESTRIBOS 1))
      (setq p1 (getpoint "\nSpecify point 1 : "))
      (setq p2 (getpoint "\nSpecify point 2 : "))
      (setvar "osmode" 0)      
      (if (and p1 p2)
	(progn
	  (setq p1x (car p1) p1y (cadr p1))
	  (setq p2x (car p2) p2y (cadr p2))
	  (if (> p1x p2x)(setq p3x p1x p1x p2x p2x p3x))
	  (if (> p1y p2y)(setq p3y p1y p1y p2y p2y p3y))
	  (setq p1 (list p1x p1y) p2 (list p2x p2y))
	  (setq lt (- p2y p1y) ht (- p2x p1x))
	  (setq l1 (* (atof evc4) lt 0.01) l2 (* (atof evc5) lt 0.01) l3 (* (atof evc6) lt 0.01))
	  
	  (if (> l1 0)
	    (progn
	      (setq pp1 (polar p1 (gra 0) (/ (- ht (atof evc7)) 2.0)))
	      (command "_line" pp1 (polar pp1 (gra 0) (atof evc7)) "")
	      (setq el (entlast))
	      (setq dl (+ p1y (atof evc1)))
	      (while (<= dl (+ p1y (atof evc1) l1 -0.01))
		(command "_copy" el "" p1 (list p1x dl))
		(setq pip1 dl)
		(setq dl (+ dl (atof evc1)))
	      )
	    )
	  )

	  (if (> l3 0)
	    (progn
	      (setq pp1 (polar p2 (gra 180) (/ (- ht (atof evc7)) 2.0)))
	      (command "_line" pp1 (polar pp1 (gra 180) (atof evc7)) "")
	      (setq el (entlast))
	      (setq dl (- p2y (atof evc3)))
	      (while (>= dl (- p2y (atof evc1) l3 -0.01))
		(command "_copy" el "" p2 (list p2x dl))
		(setq pip2 dl)
		(setq dl (- dl (atof evc3)))
	      )
	    )
	  )

	  (if (and (> l1 0) (> l2 0) (> l3 0))
	    (progn
	      (setq pip1 (+ pip1 (atof evc2)))
	      (setq pip2 (- pip2 (atof evc2)))
	      (setq lpip (- pip2 pip1))
	      (setq npip (fix (+ (/ lpip (atof evc2)) 0.01)))
	      (setq pp1 (list (+ p1x (/ (- ht (atof evc7)) 2.0)) (+ pip1 (/ (- lpip (* npip (atof evc2))) 2.0))  ))
	      (command "_line" pp1 (polar pp1 (gra 0) (atof evc7)) "")
	      (setq el (entlast))
	      (setq dl (+ (cadr pp1) (atof evc2)))
	      (while (<= dl (+ pip2 0.01))
		(command "_copy" el "" pp1 (list (car pp1) dl))
		(setq dl (+ dl (atof evc2)))
	      )
	    )
	  )
	  (BUSCALAYER "COTAS")
	  (setq p1 (polar p1 (gra 0) (+ ht 0.7)))
	  (setq p2 (polar p1 (gra 90) l1))
	  (setq p3 (polar p2 (gra 90) l2))
	  (setq p4 (polar p3 (gra 90) l3))
	  (if (> l1 0)
	    (progn
	      (command "_line" (polar p1 (gra 180) 0.10) (polar p1 (gra 0) 0.10) "")
	      (command "_rotate" (entlast) "" p1 45)
	      (command "_line" (polar p2 (gra 180) 0.10) (polar p2 (gra 0) 0.10) "")
	      (command "_rotate" (entlast) "" p2 45)
	      (command "_line" (polar p1 (gra 180) 0.10) (polar p1 (gra 0) 0.10) "")
	      (command "_line" (polar p2 (gra 180) 0.10) (polar p2 (gra 0) 0.10) "")
	      (command "_line" p1 p2 "")
	      ;SE ACTUALIZO LA VARIABLE t A t2 POR PROTECCION DE VARIABLE 2007-02-01 LC
	      (setq t7 (/ 100.0 (atof evc4)))
	      (if (= t7 (fix t7))(setq t7 (strcat "L/" (rtos t7 2 0)))(setq t7 (strcat "L/" (rtos t7 2 2))))
	      (if (eq t7 "L/1")(setq t7 "L"))
	      (setq p (mapcar '/ (mapcar '+ p1 p2) (list 2.0 2.0 2.0)))
	      (command "_text" "_j" "_c" (polar p (gra 180) 0.15) 0.10 90 t7)
	      (command "_text" "_j" "_c" (polar p (gra 180) -0.25) 0.10 90 (strcat "@" (substr evc1 2 5)))
	    )
	  )
	  (if (> l3 0)
	    (progn
	      (command "_line" (polar p3 (gra 180) 0.10) (polar p3 (gra 0) 0.10) "")
	      (command "_rotate" (entlast) "" p3 45)
	      (command "_line" (polar p4 (gra 180) 0.10) (polar p4 (gra 0) 0.10) "")
	      (command "_rotate" (entlast) "" p4 45)
	      (command "_line" (polar p3 (gra 180) 0.10) (polar p3 (gra 0) 0.10) "")
	      (command "_line" (polar p4 (gra 180) 0.10) (polar p4 (gra 0) 0.10) "")
	      (command "_line" p3 p4 "")
	      ;SE ACTUALIZO LA VARIABLE t A t2 POR PROTECCION DE VARIABLE 2007-02-01 LC
	      (setq t7 (/ 100.0 (atof evc6)))
	      (if (= t7 (fix t7))(setq t7 (strcat "L/" (rtos t7 2 0)))(setq t7 (strcat "L/" (rtos t7 2 2))))
	      (if (eq t7 "L/1")(setq t7 "L"))
	      (setq p (mapcar '/ (mapcar '+ p3 p4) (list 2.0 2.0 2.0)))
	      (command "_text" "_j" "_c" (polar p (gra 180) 0.15) 0.10 90 t7)
	      (command "_text" "_j" "_c" (polar p (gra 180) -0.25) 0.10 90 (strcat "@" (substr evc3 2 5)))
	    )
	  )
	  (if (and (> l1 0) (> l2 0) (> l3 0))
	    (progn
	      (command "_line" p2 p3 "")
	      ;SE ACTUALIZO LA VARIABLE t A t2 POR PROTECCION DE VARIABLE 2007-02-01 LC
	      (setq t7 (/ 100.0 (atof evc5)))
	      (if (= t7 (fix t7))(setq t7 (strcat "L/" (rtos t7 2 0)))(setq t7 (strcat "L/" (rtos t7 2 2))))
	      (if (eq t7 "L/1")(setq t7 "L"))
	      (setq p (mapcar '/ (mapcar '+ p2 p3) (list 2.0 2.0 2.0)))
	      (command "_text" "_j" "_c" (polar p (gra 180) 0.15) 0.10 90 t7)
	      (command "_text" "_j" "_c" (polar p (gra 180) -0.25) 0.10 90 (strcat "@" (substr evc2 2 5)))
	     )
	  )
	)
      )
      (C:DIBESTRIBOS)
    )
  )
  (setvar "cmdecho" old2)(setvar "blipmode" blipmodeANT)(setvar "clayer" layerANT)(setvar "plinewid" wideANT)(setvar "osmode" os)(setvar "plinetype" VAR_PLINETYPE)
)
;-----------------------
(DEFUN C:DIBGRADAS (/ gr11 gr22 gr33 gr44 gr55 gr66 gr77 gr88)
  ;PARA SETEAR A CERO EL VALOR DE PLINETYPE 2007-01-31 LC
  (setvar "clayer" layerdib)(setvar "cmdecho" 0)(setvar "blipmode" 0)(setvar "plinewid" 0)(setvar "osmode" 0)(setvar "plinetype" 0)
  (setq opGRADAS 0)
  (SETQ DCL3 (LOAD_DIALOG "graficos.dcl"))
  (SETQ CAJAB2 (NEW_DIALOG "gradas" DCL3))
  
  (if (= gr1 nil)(setq gr1 "7"))
  (if (= gr2 nil)(setq gr2 "0.300"))
  (if (= gr3 nil)(setq gr3 "0.180"))
  (if (= gr4 nil)(setq gr4 "1.000"))
  (if (= gr5 nil)(setq gr5 "1.200"))
  (if (= gr6 nil)(setq gr6 "0.250"))
  (if (= gr7 nil)(setq gr7 "0.200"))
  (if (= gr8 nil)(setq gr8 "0.150"))
  
  (set_tile "gr1" gr1)(set_tile "gr2" gr2)(set_tile "gr3" gr3)(set_tile "gr4" gr4)(set_tile "gr5" gr5)(set_tile "gr6" gr6)(set_tile "gr7" gr7)(set_tile "gr8" gr8)
  (tipogra2 "gradas" "gradas" "grad1" 0)
  (action_tile "gr1" "(setq gr1 (AR $value 5 0 \"gr1\")  )")
  (action_tile "gr2" "(setq gr2 (AR $value 6 3 \"gr2\")  )")
  (action_tile "gr3" "(setq gr3 (AR $value 6 3 \"gr3\")  )")
  (action_tile "gr4" "(setq gr4 (AR $value 6 3 \"gr4\")  )")
  (action_tile "gr5" "(setq gr5 (AR $value 6 3 \"gr5\")  )")
  (action_tile "gr6" "(setq gr6 (AR $value 6 3 \"gr6\")  )")
  (action_tile "gr7" "(setq gr7 (AR $value 6 3 \"gr7\")  )")
  (action_tile "gr8" "(setq gr8 (AR $value 6 3 \"gr8\")  )")
  
  (action_tile "gr9" "(setq opGRADAS 1)(done_dialog)")
  
  (START_DIALOG)
  (DONE_DIALOG)
  (cond
    ((= opGRADAS 1)
      (setq gr11 (atoi gr1) gr22 (atof gr2) gr33 (atof gr3) gr44 (atof gr4) gr55 (atof gr5) gr66 (atof gr6) gr77 (atof gr7) gr88 (atof gr8))  
      (if (< gr22 0)(setq gr44 (* gr44 -1) gr55 (* gr55 -1)))
      (setq gr8x (* gr88 (/ 1.0 gr33) (expt (+ (expt gr33 2) (expt gr22 2)) 0.5)))
      (if (< gr22 0)(setq gr8x (* gr8x -1)))
      (setq p1 (getpoint "\nSpecify point : "))
      (if p1
	(progn
	  (setq p11 p1)
	  (command "_line" p11 (setq p11 (polar p11 (gra 90) gr66))
			       (setq p01 (polar p11 (gra 0) gr44))
			       (setq p11 (polar p01 (gra 90) gr33))
	  "")
	  (repeat (1- gr11)
	    (command "_line" p11 (setq p02 (polar p11 (gra 0) gr22))
				 (setq p11 (polar p02 (gra 90) gr33))
	    "")
	  )
	  (command "_line" p11 (setq p11 (polar p11 (gra 0) gr55))
			      (setq p11 (polar p11 (gra 270) gr77))
	  "")
	  (setq p6 p11)
	  (if (< gr33 0)
	    (setq  p01 (polar p01 (gra 270) (abs gr33)) p02 (polar p02 (gra 270) (abs gr33))     )
	  )
	  (setq p01x (car p01) p01y (cadr p01))
	  (setq p02x (car p02) p02y (cadr p02))
	  
	  (setq x (+ gr8x p01x (/ (* (- (cadr p6) p01y) (- p01x p02x)) (- p01y p02y)))  )
	  (command "_line" p6 (setq a1 (list x (cadr p6))) "")
	  (setq x (+ gr8x p01x (/ (* (- (cadr p1) p01y) (- p01x p02x)) (- p01y p02y)))  )
	  (command "_line" p1 (setq a2 (list x (cadr p1))) "")
	  (command "_line" a1 a2 "")

	  (BUSCALAYER "TEXTOS")
	  (setq t1 (getreal "\nInitial level <0.00>: "))
	  (if (= t1 nil)(setq t1 0.00))
	  (setq t2 (+ t1 (* gr33 gr11)))
	  (if (>= t1 0)(setq t1 (strcat "N+" (rtos t1 2 2)))(setq t1 (strcat "N" (rtos t1 2 2))))
	  (if (>= t2 0)(setq t2 (strcat "N+" (rtos t2 2 2)))(setq t2 (strcat "N" (rtos t2 2 2))))
	  (if (> gr33 0)
	    (setq p (mapcar '- p01 (list  (/ gr44 2.0) 0.0)))
	    (setq p (mapcar '- p01 (list  (/ gr44 2.0) gr33)))
	  )
	  (command "_text" "_j" "_c" (polar p (gra 90) 0.15) 0.15 0 t1)
	  (if (> gr33 0)
	    (setq p (mapcar '+ p02 (list  (/ gr55 2.0) gr33)))
	    (setq p (mapcar '+ p02 (list  (/ gr55 2.0) 0.0)))
	  )
	  (command "_text" "_j" "_c" (polar p (gra 90) 0.15) 0.15 0 t2)
	)
      )
      (C:DIBGRADAS)
    )
  )
  (setvar "cmdecho" old2)(setvar "blipmode" blipmodeANT)(setvar "clayer" layerANT)(setvar "plinewid" wideANT)(setvar "osmode" os)(setvar "plinetype" VAR_PLINETYPE)
)
;-----------------------
(DEFUN C:DIBVARIOS ()
  ;PARA SETEAR A CERO EL VALOR DE PLINETYPE 2007-01-31 LC
  (setvar "clayer" layerdib)(setvar "cmdecho" 0)(setvar "blipmode" 0)(setvar "plinewid" 0)(setvar "osmode" 0)(setvar "plinetype" 0)
  (setq opVARIOS 0)
  (SETQ DCL3 (LOAD_DIALOG "graficos.dcl"))
  (SETQ CAJAB2 (NEW_DIALOG "varios" DCL3))
  
  (action_tile "vari1" "(setq opVARIOS 1)(done_dialog)")
  (action_tile "vari2" "(setq opVARIOS 2)(done_dialog)")
  (action_tile "vari3" "(setq opVARIOS 3)(done_dialog)")
  (action_tile "vari4" "(setq opVARIOS 4)(done_dialog)")
  
  (START_DIALOG)
  (DONE_DIALOG)
  
  (cond
    ((= opVARIOS 1)(C:NUMERARCOD)(C:DIBVARIOS))
    ((= opVARIOS 2)(C:NUMCODMAX)(C:DIBVARIOS))
    ((= opVARIOS 3)(C:DATGRA)(C:DIBVARIOS))
    ((= opVARIOS 4)
      (setq s (ssget  '((0 . "text,polyline") (-3 ("acerTX,acerPL")))))
      (if s
	(progn
	  (setq s1 (ssadd) s2 (ssadd) s3 (ssadd) s4 (ssadd) contar 0)
	  (repeat (sslength s)
	    (setq e (ssname s contar))
	    (setq s4 (ssadd e s4))
	    (setq tipoe (cdr (assoc 0 (entget e))))
	    (if (eq tipoe "TEXT")
	      (progn
		(setq le (c:llamarTX e))
		(setq e2 (handent WHPL))
		(if e2
		  (if (entget e2)
		    (setq s1 (ssadd e s1) s1 (ssadd e2 s1) s4 (ssadd e2 s4))
		    (setq s2 (ssadd e s2))
		  )
		  (setq s2 (ssadd e s2))
		)
	      )
	      (progn
		(setq le (c:llamarPL e))
		(setq e2 (handent WHNT))
		(if e2
		  (if (entget e2)
		    (setq s1 (ssadd e2 s1) s1 (ssadd e s1) s4 (ssadd e2 s4))
		    (setq s3 (ssadd e s3))
		  )
		  (setq s3 (ssadd e s3))
		)
	      )
	    )
	    (setq contar (1+ contar))
	  )                           
	  
	  (setq p1 (getpoint "\nSpecify base point :"))
	  (if p1
	    (progn
	      (command "_copy" s4 "" p1 pause)
	      (setq p2 (getvar "lastpoint"))
	      (command "_undo" "")
	      (command "_copy" s2 s3 "" p1 p2)
	      (setq contar 0)
	      (while (ssname s1 contar)
		(setq e1 (ssname s1 contar))
		(setq e2 (ssname s1 (1+ contar)))
		(c:llamarTX e1)(DATOTEXT)
		(command "_copy" e1 "" p1 p2)(setq e1 (entlast))
		(command "_copy" e2 "" p1 p2)(setq e2 (entlast))
		(setq HTX WHTX)
		(setq HPL (cdr (assoc 5 (entget e2))))
		(setq HNT (cdr (assoc 5 (entget e1))))
		(c:grabarTX e1)(c:grabarPL e2)
		
		(setq contar (+ 2 contar))
	      )
	    )
	  )
	)
      )
      
      (C:DIBVARIOS)    
    )
  )
  (setvar "cmdecho" old2)(setvar "blipmode" blipmodeANT)(setvar "clayer" layerANT)(setvar "plinewid" wideANT)(setvar "osmode" os)(setvar "plinetype" VAR_PLINETYPE)
)
;-----------------------
(DEFUN C:DIBBLOQUES ()
  ;PARA SETEAR A CERO EL VALOR DE PLINETYPE 2007-01-31 LC
  (setvar "clayer" layerdib)(setvar "cmdecho" 0)(setvar "blipmode" 0)(setvar "plinewid" 0)(setvar "osmode" os)(setvar "plinetype" 0)
  
  (if (= vizq nil)(setq vizq "0.00"))
  (if (= vder nil)(setq vder "0.00"))
  (if (= vsup nil)(setq vsup "0.00"))
  (if (= vinf nil)(setq vinf "0.00"))
  
  (if (= bl01 nil)(setq bl01 "0.40"))
  (if (= bl02 nil)(setq bl02 "0.10"))
  (if (= bl03 nil)(setq bl03 "0.40"))
  (if (= bl04 nil)(setq bl04 "0.10"))
  
  (if (= tipocx nil)(setq tipocx "0"))
  (if (= tipocy nil)(setq tipocy "0"))
  
  (setq opcionBLOQUES 0)
  (SETQ DCL3 (LOAD_DIALOG "graficos.dcl"))
  (SETQ CAJAB2 (NEW_DIALOG "bloques" DCL3))
  
  (set_tile "vizq" vizq)
  (set_tile "vder" vder)
  (set_tile "vsup" vsup)
  (set_tile "vinf" vinf)
  
  (set_tile "bl01" bl01)
  (set_tile "bl02" bl02)
  (set_tile "bl03" bl03)
  (set_tile "bl04" bl04)
  
  (set_tile "tipocx" tipocx)
  (set_tile "tipocy" tipocy)
  
  (action_tile "tipocx" "(setq tipocx (atoa $value))")
  (action_tile "tipocy" "(setq tipocy (atoa $value))")
  
  (action_tile "vizq" "(setq vizq (AR $value 5 2 \"vizq\")  )")
  (action_tile "vder" "(setq vder (AR $value 5 2 \"vder\")  )")
  (action_tile "vsup" "(setq vsup (AR $value 5 2 \"vsup\")  )")
  (action_tile "vinf" "(setq vinf (AR $value 5 2 \"vinf\")  )")
  
  (action_tile "bl01" "(setq bl01 (AR $value 5 2 \"bl01\")  )")
  (action_tile "bl02" "(setq bl02 (AR $value 5 2 \"bl02\")  )")
  (action_tile "bl03" "(setq bl03 (AR $value 5 2 \"bl03\")  )")
  (action_tile "bl04" "(setq bl04 (AR $value 5 2 \"bl04\")  )")
  
  (action_tile "dibbloques" "(setq opcionBLOQUES 1)(done_dialog)")
  (action_tile "dibalib"    "(setq opcionBLOQUES 2)(done_dialog)")
  (action_tile "dibborb"    "(setq opcionBLOQUES 3)(done_dialog)")
  
  (START_DIALOG)
  (DONE_DIALOG)
  
  (cond
    ((= opcionBLOQUES 1)
      (DIBBLOQUES)(C:DIBBLOQUES)
    )
    ((= opcionBLOQUES 2)
      (DIBALIB)(C:DIBBLOQUES)
    )
    ((= opcionBLOQUES 3)
      (setq s (ssget  (list (cons 0 "line,polyline")(cons 8 layerdib))))
      (command "_erase" s "")
      (C:DIBBLOQUES)
    )
  )
  (setvar "cmdecho" old2)
  (setvar "blipmode" blipmodeANT)
  (setvar "clayer" layerANT)
  (setvar "plinewid" wideANT)
  ;AQUI ASIGNO LA VARIABLE ANTERIOR DE PLINETYPE 2007-01-31 LC
  (setvar "plinetype" VAR_PLINETYPE)
)  
;-----------------------
(DEFUN DIBALIB ()
  (setq s (ssget  (list (cons 0 "line,polyline")(cons 8 layerdib))))
  (if s
    (progn
      (INITGET "alinearX alinearY Salir")
      (setq opAL (GETKWORD "\nSelect Align : X/Y/<Exit> : "))
      (cond
	((= opAL "alinearX")
	  (setq p1 (getpoint "\nSpecify base point : "))
	  (setq p2 (getpoint "\nSpecify align X point : "))
	  (if (and p1 p2)
	    (progn
	      (setq p1x (car p1) p1y (cadr p1))
	      (setq p2x (car p2) p2y (cadr p2))
	      (command "_move" s "" p1 (list p2x p1y))
	    )
	  )
	)
	((= opAL "alinearY")
	  (setq p1 (getpoint "\nSpecify base point [end]: "))
	  (setq p2 (getpoint "\nSpecify align Y point [end] : "))
	  (if (and p1 p2)
	    (progn
	      (setq p1 (osnap p1 "end") p2 (osnap p2 "end"))
	      (setq p1x (car p1) p1y (cadr p1))
	      (setq p2x (car p2) p2y (cadr p2))
	      (command "_move" s "" p1 (list p1x p2y))
	    )
	  )
	)
      )
    )
  )
)  
;-----------------------
(DEFUN DIBBLOQUES (/ bl1 bl2 bl3 bl4 POINT_1_X POINT_1_Y POINT_2_X POINT_2_Y DIST_A DIST_B DIST_C DIST_D POINT_1 POINT_2)
  (SETQ DIST_A (atof vizq))
  (SETQ DIST_B (atof vsup))
  (SETQ DIST_C (atof vder))
  (SETQ DIST_D (atof vinf))
  
  (SETQ bl1 (atof bl01))
  (SETQ bl2 (atof bl02))
  (SETQ bl3 (atof bl03))
  (SETQ bl4 (atof bl04))
  
  (SETQ POINT_1 (GETPOINT "\nSpecify point 1: "))
  (SETQ POINT_2 (GETPOINT "\nSpecify point 2: "))
  
  (if (and POINT_1 POINT_2)
    (progn
      (SETQ POINT_1_X (CAR POINT_1))
      (SETQ POINT_1_Y (CAR (CDR POINT_1)))
      (SETQ POINT_2_X (CAR POINT_2))
      (SETQ POINT_2_Y (CAR (CDR POINT_2)))
      (IF (> POINT_1_X POINT_2_X)
	(SETQ X1 POINT_2_X X2 POINT_1_X)
	(SETQ X1 POINT_1_X X2 POINT_2_X)
      )
      (IF (> POINT_1_Y POINT_2_Y)
	(SETQ Y1 POINT_2_Y Y2 POINT_1_Y)
	(SETQ Y1 POINT_1_Y Y2 POINT_2_Y)
      )
      (SETQ DX (- X2 X1 DIST_A DIST_C))
      (SETQ DY (- Y2 Y1 DIST_B DIST_D))
      (SETQ NUM_B_X (FIX (/ (+ DX 0.1) (+ bl1 bl2))))
      (SETQ NUM_B_Y (FIX (/ (+ DY 0.1) (+ bl3 bl4))))
      (SETQ DCX (/ (- DX (* (+ bl1 bl2) NUM_B_X) (* bl2 -1.0)) 2.0))
      (SETQ DCY (/ (- DY (* (+ bl3 bl4) NUM_B_Y) (* bl4 -1.0)) 2.0))

      (IF (= tipocx "0")
	(SETQ POINT_I_X (+ X1 DIST_A DCX))
	(SETQ POINT_I_X (+ X1 DIST_A))
      )
      (IF (= tipocy "0")
	(SETQ POINT_I_Y (+ Y1 DIST_D DCY))
	(SETQ POINT_I_Y (+ Y1 DIST_D))
      )
  
      (IF (= tipocx "1")
	(progn
	  (SETQ POINT_I_X (getpoint "\nSpecify align X point : "))
	  (if (= POINT_I_X nil)
	    (setq POINT_I_X (+ X1 DIST_A))
	    (setq POINT_I_X (CAR POINT_I_X))
	  ) 
	)
      )
      (IF (= tipocy "1")
	(progn
	  (SETQ POINT_I_Y (getpoint "\nSpecify align Y point : "))
	  (if (= POINT_I_Y nil)
	    (setq POINT_I_Y (+ Y1 DIST_D))
	    (setq POINT_I_Y (CAR (CDR POINT_I_Y)))
	  ) 
	)
      )
      (if (/= os 0)(command "_osnap" "_none"))
  
      (COMMAND "_PLINE" (SETQ P1 (LIST POINT_I_X POINT_I_Y))
		       (SETQ P2 (POLAR P1 (GRA 0) bl1))
		       (SETQ P3 (POLAR P2 (GRA 90) bl3))
		       (SETQ P4 (POLAR P3 (GRA 180) bl1))
		       "_C" 
      )
      (COMMAND "_ARRAY" "_L" "" "_R" NUM_B_Y NUM_B_X (+ bl3 bl4) (+ bl1 bl2))
      (setvar "osmode" os)
    )
  )
)
